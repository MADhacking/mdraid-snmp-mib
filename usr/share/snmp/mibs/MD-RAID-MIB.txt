MD-RAID-MIB DEFINITIONS ::= BEGIN

-- imports and exports

IMPORTS
    MODULE-COMPLIANCE, OBJECT-GROUP
        FROM SNMPv2-CONF
    MODULE-IDENTITY, OBJECT-TYPE, Integer32, Gauge32
        FROM SNMPv2-SMI
    DisplayString, TruthValue
        FROM SNMPv2-TC
    hackingInternal, hackingExperimental
        FROM HACKING-SNMP-MIB;

mdRaidMIB MODULE-IDENTITY
	LAST-UPDATED 	"201610190000Z"
	ORGANIZATION 	"Hacking Networked Solutions Ltd"
	CONTACT-INFO	"Max Hacking"
	DESCRIPTION		"This MIB module defines objects for MD RAID data."
	REVISION     	"201610190000Z"
	DESCRIPTION		"Added mdRaidArrayRaidComponents"
	REVISION     	"201110080000Z"
	DESCRIPTION		"First version"
    ::= { mdRaid 1 }

mdRaid                  OBJECT IDENTIFIER ::= { hackingExperimental 2 }
mdRaidMIBConformance    OBJECT IDENTIFIER ::= { hackingInternal 2 }

--

mdRaidTable OBJECT-TYPE
    SYNTAX      SEQUENCE OF SmdRaidArrayEntry
    MAX-ACCESS  not-accessible
    STATUS      current
    DESCRIPTION "Table of MD RAID information."
    ::= { mdRaid 2 }

mdRaidArrayEntry OBJECT-TYPE
    SYNTAX      SmdRaidArrayEntry
    MAX-ACCESS  not-accessible
    STATUS      current
    DESCRIPTION "An entry containing a device and its statistics."
    INDEX       { mdRaidArrayIndex }
    ::= { mdRaidTable 1 }
    
    SmdRaidArrayEntry ::= SEQUENCE {
   	mdRaidArrayIndex					Integer32,
   	mdRaidArrayDev						DisplayString,
   	mdRaidArrayVersion					DisplayString,
   	mdRaidArrayUUID						DisplayString,
   	mdRaidArrayLevel					DisplayString,
   	mdRaidArrayLayout					DisplayString,
   	mdRaidArrayChunkSize				DisplayString,
   	mdRaidArraySize						DisplayString,
   	mdRaidArrayDeviceSize				DisplayString,
   	mdRaidArrayHealthOK					TruthValue,
   	mdRaidArrayHasFailedComponents		TruthValue,
   	mdRaidArrayHasAvailableSpares		TruthValue,
   	mdRaidArrayTotalComponents   		Gauge32,
   	mdRaidArrayActiveComponents   		Gauge32,
   	mdRaidArrayWorkingComponents  		Gauge32,
   	mdRaidArrayFailedComponents   		Gauge32,
   	mdRaidArraySpareComponents			Gauge32,
   	mdRaidArrayRaidComponents			Gauge32
}

--   
    
mdRaidArrayIndex OBJECT-TYPE
    SYNTAX      Integer32 (0..65535)
    MAX-ACCESS  read-only
    STATUS      current
    DESCRIPTION "Reference index for each observed array."
    ::= { mdRaidArrayEntry 1 }
    
mdRaidArrayDev OBJECT-TYPE
    SYNTAX      DisplayString
    MAX-ACCESS  read-only
    STATUS      current
    DESCRIPTION "The path to the DEV entry for this array."
    ::= { mdRaidArrayEntry 2 }
    
mdRaidArrayVersion OBJECT-TYPE
    SYNTAX      DisplayString
    MAX-ACCESS  read-only
    STATUS      current
    DESCRIPTION "The super-block version used by this array."
    ::= { mdRaidArrayEntry 3 }

mdRaidArrayUUID OBJECT-TYPE
    SYNTAX      DisplayString
    MAX-ACCESS  read-only
    STATUS      current
    DESCRIPTION "The UUID string for this array."
    ::= { mdRaidArrayEntry 4 }
    
mdRaidArrayLevel OBJECT-TYPE
    SYNTAX      DisplayString
    MAX-ACCESS  read-only
    STATUS      current
    DESCRIPTION "The RAID level employed by this array."
    ::= { mdRaidArrayEntry 5 }
    
mdRaidArrayLayout OBJECT-TYPE
    SYNTAX      DisplayString
    MAX-ACCESS  read-only
    STATUS      current
    DESCRIPTION "The RAID layout employed by this array."
    ::= { mdRaidArrayEntry 6 }

mdRaidArrayChunkSize OBJECT-TYPE
    SYNTAX      DisplayString
    MAX-ACCESS  read-only
    STATUS      current
    DESCRIPTION "The chunk size used by this array."
    ::= { mdRaidArrayEntry 7 }

mdRaidArraySize OBJECT-TYPE
    SYNTAX      DisplayString
    MAX-ACCESS  read-only
    STATUS      current
    DESCRIPTION "The size of this array."
    ::= { mdRaidArrayEntry 8 }

mdRaidArrayDeviceSize OBJECT-TYPE
    SYNTAX      DisplayString
    MAX-ACCESS  read-only
    STATUS      current
    DESCRIPTION "The device size of this array."
    ::= { mdRaidArrayEntry 9 }

mdRaidArrayHealthOK OBJECT-TYPE
    SYNTAX      TruthValue
    MAX-ACCESS  read-only
    STATUS      current
    DESCRIPTION "The current health status reported by this array."
    ::= { mdRaidArrayEntry 10 }

mdRaidArrayHasFailedComponents OBJECT-TYPE
    SYNTAX      TruthValue
    MAX-ACCESS  read-only
    STATUS      current
    DESCRIPTION "TRUE if this array has failed components, FALSE if all components are functioning."
    ::= { mdRaidArrayEntry 11 }

mdRaidArrayHasAvailableSpares OBJECT-TYPE
    SYNTAX      TruthValue
    MAX-ACCESS  read-only
    STATUS      current
    DESCRIPTION "TRUE if this array has available spares, FALSE if no spare devices are available."
    ::= { mdRaidArrayEntry 12 }

mdRaidArrayTotalComponents OBJECT-TYPE
    SYNTAX      Gauge32
    MAX-ACCESS  read-only
    STATUS      current
    DESCRIPTION "The total number of component devices currently associated with this array."
    ::= { mdRaidArrayEntry 13 }

mdRaidArrayActiveComponents OBJECT-TYPE
    SYNTAX      Gauge32
    MAX-ACCESS  read-only
    STATUS      current
    DESCRIPTION "The number of active component devices in use by this array."
    ::= { mdRaidArrayEntry 14 }

mdRaidArrayWorkingComponents OBJECT-TYPE
    SYNTAX      Gauge32
    MAX-ACCESS  read-only
    STATUS      current
    DESCRIPTION "The number of working component devices in use by this array."
    ::= { mdRaidArrayEntry 15 }

mdRaidArrayFailedComponents OBJECT-TYPE
    SYNTAX      Gauge32
    MAX-ACCESS  read-only
    STATUS      current
    DESCRIPTION "The number of failed component devices associated with this array."
    ::= { mdRaidArrayEntry 16 }

mdRaidArraySpareComponents OBJECT-TYPE
    SYNTAX      Gauge32
    MAX-ACCESS  read-only
    STATUS      current
    DESCRIPTION "The number of spare component devices available for use by this array."
    ::= { mdRaidArrayEntry 17 }

mdRaidArrayRaidComponents OBJECT-TYPE
    SYNTAX      Gauge32
    MAX-ACCESS  read-only
    STATUS      current
    DESCRIPTION "The total number of component devices required for this array."
    ::= { mdRaidArrayEntry 18 }

-- Conformance information ******************************************

mdRaidMIBCompliances OBJECT IDENTIFIER ::= {mdRaidMIBConformance 1}
mdRaidMIBGroups      OBJECT IDENTIFIER ::= {mdRaidMIBConformance 2}

-- Compliance statements

mdRaidCompliance MODULE-COMPLIANCE
    STATUS       current
    DESCRIPTION "The compliance statement for SNMP entities which
                 implement the mdRaid-MIB."

    MODULE    -- this module
        MANDATORY-GROUPS { mdRaidGroup }
    ::= { mdRaidMIBCompliances 1 }

mdRaidGroup OBJECT-GROUP
    OBJECTS 
    {
        mdRaidArrayIndex,
        mdRaidArrayDev,
        mdRaidArrayVersion,
        mdRaidArrayUUID,
        mdRaidArrayLevel,
        mdRaidArrayLayout,
        mdRaidArrayChunkSize,
        mdRaidArraySize,
        mdRaidArrayDeviceSize,
        mdRaidArrayHealthOK,
        mdRaidArrayHasFailedComponents,
        mdRaidArrayHasAvailableSpares,
        mdRaidArrayTotalComponents,
        mdRaidArrayActiveComponents,
        mdRaidArrayWorkingComponents,
        mdRaidArrayFailedComponents,
        mdRaidArraySpareComponents,
        mdRaidArrayRaidComponents
    }
    STATUS       current
    DESCRIPTION "A collection of objects providing for remote
                 monitoring of MD-RAID health data."
    ::= { mdRaidMIBGroups 1 }

END
